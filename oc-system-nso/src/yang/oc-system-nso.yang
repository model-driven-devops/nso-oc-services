module oc-system-nso {

  namespace "http://cisco.com/oc-system-nso";
  prefix oc-system-nso;

  import ietf-inet-types {
    prefix inet;
  }
  import tailf-common {
    prefix tailf;
  }
  import tailf-ncs {
    prefix ncs;
  }
  import openconfig-system {
    prefix oc-sys;
  }
  description
    "Model to include openconfig-system in an NSO service";

  revision 2021-06-09 {
    description
      "Augmented:
      nso-enable-secret,
      nso-console-exec-timeout-seconds,
      nso-ntp-enable-logging,
      nso-ntp-use-vrf,
      nso-ntp-auth-key-id,
      nso-absolute-timeout-minutes,
      nso-ssh-timeout,
      nso-ssh-source-interface,
      nso-use-vrf";
  }

  revision 2021-05-11 {
    description
      "Initial revision.";
  }

  list oc-system-nso {
    description "Accepts items composed of service name, device name, and openconfig system model";

    key name;
    leaf name {
      tailf:info "Unique service id";
      tailf:cli-allow-range;
      type string;
    }

    uses ncs:service-data;
    ncs:servicepoint oc-system-nso-servicepoint;

    leaf device {
      type leafref {
        path "/ncs:devices/ncs:device/ncs:name";
      }
    }

    container openconfig-system {
      uses oc-sys:system-top;
    }
  }
     augment /oc-system-nso:oc-system-nso/openconfig-system/system/config {
      leaf nso-enable-secret {
        type string;
        description
          "Sets a local password to control access to various privilege levels.
          At this time, only encryption-type 0 is supported.";
      }
    }
     augment /oc-system-nso:oc-system-nso/openconfig-system/system/config {
      leaf nso-console-exec-timeout-seconds {
        type string;
        description
          "Configure the inactive session timeout on the console port in seconds.";
      }
    }
    augment /oc-system-nso:oc-system-nso/openconfig-system/system/ntp/config {
      leaf nso-ntp-enable-logging {
        type boolean;
        description
          "Enables Network Time Protocol (NTP) message logging.";
      }
    }
     augment /oc-system-nso:oc-system-nso/openconfig-system/system/ntp/servers/server {
      leaf nso-ntp-use-vrf {
        type string;
        description
          "VRF for communication with NTP servers.";
      }
    }
     augment /oc-system-nso:oc-system-nso/openconfig-system/system/ntp/servers/server/config {
      leaf nso-ntp-auth-key-id {
        type string;
        description
          "Links to authentication key in openconfig-system/system/ntp/ntp-keys";
      }
    }
     augment /oc-system-nso:oc-system-nso/openconfig-system/system/ssh-server/config {
      leaf nso-absolute-timeout-minutes {
        type string;
        description
          "The absolute timeout for line disconnection in minutes.";
      }
    }
     augment /oc-system-nso:oc-system-nso/openconfig-system/system/ssh-server/config {
      leaf nso-ssh-timeout {
        type string;
        description
          "Secure Shell (SSH) control parameter to set the time interval that the router waits for the SSH client to respond.
          In IOS, seconds from 1-120.";
      }
    }
     augment /oc-system-nso:oc-system-nso/openconfig-system/system/ssh-server/config {
      leaf nso-ssh-source-interface {
        type string;
        description
          "Secure Shell (SSH) control parameter to set the time interval that the router waits for the SSH client to respond.
          In IOS, seconds from 1-120.";
      }
    }
     augment /oc-system-nso:oc-system-nso/openconfig-system/system/logging/remote-servers/remote-server/config {
      leaf nso-use-vrf {
        type string;
        description
          "VRF from which to reach the logging servers. '' for no VRF.";
      }
    }
}
