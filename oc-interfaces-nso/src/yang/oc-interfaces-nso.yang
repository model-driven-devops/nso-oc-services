module oc-interfaces-nso {

  namespace "http://cisco.com/oc-interfaces-nso";
  prefix oc-interfaces-nso;

  import ietf-inet-types {
    prefix inet;
  }
  import tailf-common {
    prefix tailf;
  }
  import tailf-ncs {
    prefix ncs;
  }
  import iana-if-type {
    prefix ianaift;
  }
  import openconfig-if-ethernet {
    prefix oc-eth;
  }
  import openconfig-if-poe {
    prefix oc-poe;
  }
  import openconfig-if-aggregate {
    prefix oc-lag;
  }
   import openconfig-if-ip {
    prefix oc-ip;
  }
   import openconfig-vlan {
    prefix oc-vlan;
  }
  import openconfig-interfaces {
    prefix oc-if;
  }

  description
    "Model to include openconfig-interfaces in an NSO service";

  revision 2016-01-01 {
    description
      "Initial revision.";
  }

  list oc-interfaces-nso {
    description "Accepts items composed of service name, device name, and openconfig interfaces model";

    key name;
    leaf name {
      tailf:info "Unique service id";
      tailf:cli-allow-range;
      type string;
    }

    uses ncs:service-data;
    ncs:servicepoint oc-interfaces-nso-servicepoint;

    leaf device {
      type leafref {
        path "/ncs:devices/ncs:device/ncs:name";
      }
    }

    container openconfig-interfaces {
      uses oc-if:interfaces-top;
    }
  }

  // Needed to point selection options to the new model
  deviation "/oc-interfaces-nso:oc-interfaces-nso/openconfig-interfaces/interfaces/interface/ethernet/config/aggregate-id" {
    description
    "Specify the logical aggregate interface to which
        this interface belongs";
    deviate replace {
      type leafref {
      path "/oc-interfaces-nso:oc-interfaces-nso/openconfig-interfaces/interfaces/interface/name";
      }
    }
  }

  // openconfig-if-ethernet augments
  augment "/oc-interfaces-nso:oc-interfaces-nso/openconfig-interfaces/interfaces/interface" {
    description "Adds additional Ethernet-specific configuration to
    interfaces model";
    uses oc-eth:ethernet-top {
      when "current()/config/type = 'ianaift:ethernetCsmacd' or current()/config/type = 'ianaift:l2vlan'" {
      description "Additional interface configuration parameters when
      the interface type is Ethernet";
      }
    }
  }

  // openconfig-if-poe augments
  augment "/oc-interfaces-nso:oc-interfaces-nso/openconfig-interfaces/interfaces/interface/ethernet" {
    description
    "Adds PoE to the ethernet model.";
    uses oc-poe:poe-ethernet-top;
  }

  // openconfig-if-ip augments
  augment  "/oc-interfaces-nso:oc-interfaces-nso/openconfig-interfaces/interfaces/interface/config" {
    description
      "IPv4 address family configuration for
      port channels";
    uses oc-ip:ipv4-top;
  }
  augment  "/oc-interfaces-nso:oc-interfaces-nso/openconfig-interfaces/interfaces/interface/aggregation" {
    description
      "IPv4 address family configuration for
      port channels";
    uses oc-ip:ipv4-top;
  }
  augment  "/oc-interfaces-nso:oc-interfaces-nso/openconfig-interfaces/interfaces/interface/subinterfaces/subinterface" {
    description
      "IPv4 address family configuration for
      interfaces";
    uses oc-ip:ipv4-top;
  }
  augment "/oc-interfaces-nso:oc-interfaces-nso/openconfig-interfaces/interfaces/interface/subinterfaces/subinterface" {
    description
      "IPv6 address family configuration for
      interfaces";
    uses oc-ip:ipv6-top;
  }
  augment "/oc-interfaces-nso:oc-interfaces-nso/openconfig-interfaces/interfaces/interface/subinterfaces/subinterface/ipv4/addresses/address" {
    description
      "Additional IP addr family configuration for
      interfaces";
    uses oc-ip:ip-vrrp-top;
  }
  augment "/oc-interfaces-nso:oc-interfaces-nso/openconfig-interfaces/interfaces/interface/subinterfaces/subinterface/ipv6/addresses/address" {
    description
      "Additional IP addr family configuration for
      interfaces";
    uses oc-ip:ip-vrrp-top;
  }
  augment "/oc-interfaces-nso:oc-interfaces-nso/openconfig-interfaces/interfaces/interface/subinterfaces/subinterface/ipv6/addresses/address/vrrp/vrrp-group/config" {
    description
      "Additional VRRP data for IPv6 interfaces";
    uses oc-ip:ip-vrrp-ipv6-config;
  }

  // openconfig-if-aggregate augments
  augment "/oc-interfaces-nso:oc-interfaces-nso/openconfig-interfaces/interfaces/interface" {
    when "(current()/config/type = 'ianaift:ieee8023adLag' or current()/config/type = 'ianaift:propVirtual') and"+
         " not (contains(current()/config/name, 'LISP'))"+
         " and not (contains(current()/config/name, 'VirtualPortGroup'))" {
      description "active when the interface is set to type LAG";
    }
    description "Adds LAG configuration to the interface module";
    uses oc-lag:aggregation-logical-top;
  }
  augment "/oc-interfaces-nso:oc-interfaces-nso/openconfig-interfaces/interfaces/interface/ethernet/config" {
    description "Adds LAG settings to individual Ethernet
    interfaces";
    uses oc-lag:ethernet-if-aggregation-config;
  }

  // openconfig-vlan augments
   augment "/oc-interfaces-nso:oc-interfaces-nso/openconfig-interfaces/interfaces/interface/subinterfaces/subinterface" {
      description
        "Adds VLAN settings to individual subinterfaces";
    uses oc-vlan:vlan-logical-top;
  }
  augment "/oc-interfaces-nso:oc-interfaces-nso/openconfig-interfaces/interfaces/interface/ethernet" {
    description
      "Adds VLAN settings to individual Ethernet interfaces";
    uses oc-vlan:vlan-switched-top;
  }
  augment "/oc-interfaces-nso:oc-interfaces-nso/openconfig-interfaces/interfaces/interface/aggregation" {
    description "Adds VLAN settings to a LAG interface";
    uses oc-vlan:vlan-switched-top;
  }
  augment "/oc-interfaces-nso:oc-interfaces-nso/openconfig-interfaces/interfaces/interface" {
    description
      "Adds configuration and state for routed VLAN interfaces";
    uses oc-vlan:vlan-routed-top {
      when "current()/config/type = 'ianaift:l3ipvlan'" {
      description
        "Active when the interface is a logical interface providing
        L3 routing for VLANs";
      }
    }
  }

  // openconfig-if-ip augments
  augment "/oc-interfaces-nso:oc-interfaces-nso/openconfig-interfaces/interfaces/interface/routed-vlan" {
    description
      "IPv4 address family configuration for
      interfaces";
    uses oc-ip:ipv4-top;
  }
  augment "/oc-interfaces-nso:oc-interfaces-nso/openconfig-interfaces/interfaces/interface/routed-vlan" {
    description
      "IPv6 address family configuration for
      interfaces";
    uses oc-ip:ipv6-top;
  }
  augment "/oc-interfaces-nso:oc-interfaces-nso/openconfig-interfaces/interfaces/interface/routed-vlan/ipv4/addresses/address" {
    description
      "Additional IP addr family configuration for
      interfaces";
    uses oc-ip:ip-vrrp-top;
  }
  augment "/oc-interfaces-nso:oc-interfaces-nso/openconfig-interfaces/interfaces/interface/routed-vlan/ipv6/addresses/address" {
    description
      "Additional IP addr family configuration for
      interfaces";
    uses oc-ip:ip-vrrp-top;
  }
  augment "/oc-interfaces-nso:oc-interfaces-nso/openconfig-interfaces/interfaces/interface/routed-vlan/ipv6/addresses/address/vrrp/vrrp-group/config" {
    description
      "Additional VRRP data for IPv6 interfaces";
    uses oc-ip:ip-vrrp-ipv6-config;
  }
}
