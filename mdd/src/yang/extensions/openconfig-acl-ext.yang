module openconfig-acl-ext{

  yang-version "1.1";

  // namespace
  namespace "http://cisco.com/openconfig-acl-ext";

  prefix "oc-acl-ext";

  import tailf-ncs { prefix ncs; }
  import tailf-common { prefix tailf; }
  import mdd { prefix mdd; }
  import openconfig-acl { prefix oc-acl; }
  import openconfig-inet-types { prefix oc-inet; }
  // meta
  organization "Cisco";

  contact
    "www.cisco.com";

  description
    "Augmentation to openconfig acl model.";
  revision "2023-07-21" {
    description
      "Added support for forwarding-type of remark to support ACL remarks";
  }
  revision "2023-06-23" {
    description
      "Added support for ICMP message types and codes";
  }
  revision "2022-09-27" {
    description
      "Added config container and fixed typo";
  }
  revision "2021-10-26" {
    description
      "Initial revision";
  }
  identity REMARK {
    base oc-acl:FORWARDING_ACTION;
    description
      "Access-list entry is a remark only";
  }
  identity ACL_IPV4_STANDARD {
    base oc-acl:ACL_TYPE;
    description
      "Standard IP-layer ACLs with IPv4 addresses";
  }
  augment /ncs:devices/ncs:device/mdd:openconfig/oc-acl:acl/oc-acl:acl-sets/oc-acl:acl-set/oc-acl:acl-entries/oc-acl:acl-entry {
    container ipv4 {
      container config {
        leaf source-address {
          type oc-inet:ipv4-prefix;
          description
            "Source IPv4 address prefix.";
          when "../../../../../oc-acl:config/oc-acl:type='oc-acl-ext:ACL_IPV4_STANDARD'" ;
          }
        when "../../../../oc-acl:config/oc-acl:type='oc-acl-ext:ACL_IPV4_STANDARD'" ;
        }
     }
  }
  augment /ncs:devices/ncs:device/mdd:openconfig/oc-acl:acl/oc-acl:acl-sets/oc-acl:acl-set/oc-acl:acl-entries/oc-acl:acl-entry {
      when "./oc-acl:ipv4/oc-acl:config/oc-acl:protocol='oc-pkt-match-types:IP_ICMP'" ;
      container icmp-v4 {
        container config {
          description
            "Configuration ICMPv4 types and codes";
          leaf type {
            type uint8;
            description
              "ICMP message type.";
          }
          leaf code {
            type uint8;
            description
              "ICMP message code.";
          }
        }
      }
    }
  augment /ncs:devices/ncs:device/mdd:openconfig/oc-acl:acl {
    container ntp {
      description
        "Container for NTP ACL application.";
      container peer {
        container config {
          description
            "Configuration for ACL for NTP peer";
          leaf peer-acl-set {
            type leafref {
              path "../../../../oc-acl:acl-sets/oc-acl:acl-set/oc-acl:config/oc-acl:name";
            }
            description
              "Name of standard ACL to apply to peer.";
          }
        }
      }
      container server {
        container config {
          description
            "Configuration for ACL for NTP server";
          leaf server-acl-set {
            type leafref {
              path "../../../../oc-acl:acl-sets/oc-acl:acl-set/oc-acl:config/oc-acl:name";
            }
            description
              "Name of standard ACL to apply to server.";
          }
        }
      }
    }
    container lines {
      description
        "Enclosing container for the list of device lines on which
        ACLs are set";

      list line {
        key "id";
        description
          "List of interfaces on which ACLs are set";

        leaf id {
          type leafref {
            path "../config/id";
          }
          description
            "Name of line, e.g. 'vty 0 4'";
        }
        container config {
          description
            "Configuration for ACL per-line data";

          leaf id {
            type string;
            tailf:info "ios example: 'vty 0 4'";
            description
              "Name of line, e.g. 'vty 0 4'";
          }
        }
        container ingress-acl-sets {
              description
        "Top level container for ingress-acl-sets";

          list ingress-acl-set {
            key "ingress-acl-set-name";
            description
              "List of ingress ACLs on the line";
            leaf ingress-acl-set-name {
              type leafref {
                path "../config/ingress-acl-set-name";
              }
              description
                "Name of line ingress ACL on the line";
            }
            container config {
              description
                "Configuration for ACL per-line data";

              leaf vrf {
                type string;
                //default global;
                tailf:info "ios example: 'access-class XX in vrfname abc'";
                description
                  "Name of vrf, e.g. 'access-class XX in vrfname abc'";
              }
              leaf vrf-also {
                type boolean;
                //default false;
                tailf:info "ios example: 'access-class xxx in vrf-also '";
                description
                  "Allows access from VRFs as allowed in ACL";
              }
              leaf ingress-acl-set-name {
                type leafref {
                  path "../../../../../../oc-acl:acl-sets/oc-acl:acl-set/oc-acl:config/oc-acl:name";
                }
                description
                  "Name of line ingress ACL on the line";
              }
            }
          }
        }
        leaf egress-acl-set {
          type leafref {
            path "../../../oc-acl:acl-sets/oc-acl:acl-set/oc-acl:config/oc-acl:name";
          }
          description
            "Name of line egress ACL on the line";
        }
      }
    }
  }
}
