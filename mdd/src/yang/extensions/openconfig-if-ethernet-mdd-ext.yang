module openconfig-if-ethernet-mdd-ext {

  yang-version "1.1";

  // namespace
  namespace "http://cisco.com/openconfig-if-ethernet-mdd-ext";

  prefix "oc-if-ethernet-mdd-ext";

  import tailf-ncs { prefix ncs; }
  import tailf-common { prefix tailf; }
  import mdd { prefix mdd; }
  import openconfig-interfaces { prefix oc-if; }
  import openconfig-if-ethernet { prefix oc-eth; }
  import openconfig-inet-types { prefix oc-inet; }
  import openconfig-if-tunnel { prefix oc-tun; }
  // meta
  organization "Cisco";

  contact
    "www.cisco.com";

  description
    "Augmentation to openconfig of ethernet model.";

  revision "2023-06-30" {
    description
      "Implement IP Source Guard";
  }
  revision "2023-06-28" {
    description
      "Implement unknown flood blocking";
  }
  revision "2023-01-17" {
    description
      "Initial revision";
  }

  grouping storm-control-extensions {
    description
      "Top-level grouping for Storm Control";
    container storm-control {
      description
        "Enclosing container for storm-control handled by this interface";
      container broadcast {
        description
          "Enclosing container for broadcast address storm control";
        container level {
          description
            "Enclosing container - set storm suppression level on this interface";
          container config {
            description
              "Configuration data for storm-control";
            leaf suppression-type {
              type enumeration {
                enum NONE;
                enum BPS;
                enum PPS;
               }
               //default NONE;
               description
                 "Select the broadcast suppression type.";
            }
            leaf bps {
              when "../suppression-type = 'BPS'" {
                description
                  "Suppression level in bits per second";
              }
              type string;
            }
            leaf pps {
              when "../suppression-type = 'PPS'" {
                description
                  "Suppression level in packets per second";
              }
              type string;
            }
          }
        }
      }
      container unicast {
        description
          "Enclosing container for unicast address storm control";
        container level {
          description
            "Enclosing container - set storm suppression level on this interface";
          container config {
            description
              "Configuration data for storm-control";
            leaf suppression-type {
              type enumeration {
                enum NONE;
                enum BPS;
                enum PPS;
               }
               //default NONE;
               description
                 "Select the unicast suppression type.";
            }
            leaf bps {
              when "../suppression-type = 'BPS'" {
                description
                  "Suppression level in bits per second";
              }
              type uint64 {
                range 0..400000000000;
              }
            }
            leaf pps {
              when "../suppression-type = 'PPS'" {
                description
                  "Suppression level in packets per second";
              }
              type uint64 {
                range 0..400000000000;
              }
            }
          }
        }
      }
    }
  }

  grouping unknown-flood-blocking-extension {
    description
      "Top-level grouping for Unknown Flood Blocking (Unicast and Multicast)";
    container unknown-flood-blocking {
      description
        "Enclosing container for unknown flood blocking handled by this interface";
      container config {
        description
          "Configuration data for unknown flood blocking";
        leaf unicast {
          type enumeration {
            enum ENABLED;
            enum DISABLED;
          }
          //default DISABLED;
          description
            "Select Unknown Unicast Flood Blocking.";
        }
        leaf multicast {
          type enumeration {
            enum ENABLED;
            enum DISABLED;
          }
          //default DISABLED;
          description
           "Select Unknown Multicast Flood Blocking.";
        }
      }
    }
  }

  grouping ip-source-guard-extensions {
    description
      "Top-level grouping for IP Source Guard";
    container ip-source-guard {
      description
        "Enclosing container for IP Source Guard handled by this interface";
      container config {
        description
          "Configuration data for IP Source Guard";
        leaf ip-source-guard {
          type enumeration {
            enum ENABLED;
            enum DISABLED;
          }
          //default DISABLED;
          description
            "Select IP Source Guard.";
        }
      }
    }
  }

  // augment statements

  augment "/ncs:devices/ncs:device/mdd:openconfig/oc-if:interfaces/oc-if:interface/oc-eth:ethernet" {
    description
      "MDD extensions to ethernet interfaces";

    uses storm-control-extensions;
    uses unknown-flood-blocking-extension;
    uses ip-source-guard-extensions;
  }
}
