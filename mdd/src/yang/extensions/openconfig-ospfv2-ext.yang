module openconfig-ospfv2-ext{

  yang-version "1.1";

  // namespace
  namespace "http://cisco.com/openconfig-ospfv2-ext";

  prefix "oc-ospfv2-ext";

  import tailf-ncs { prefix ncs; }
  import tailf-common { prefix tailf; }
  import mdd { prefix mdd; }
  import openconfig-network-instance { prefix "oc-netinst"; }
  import openconfig-extensions { prefix oc-ext; }
  import openconfig-routing-policy { prefix oc-rpol; }
  import openconfig-system { prefix oc-sys; }
  import openconfig-system-ext { prefix oc-system-ext; }


  // meta
  organization "Cisco";

  contact
    "www.cisco.com";

  description
    "Augmentation to openconfig ospfv2 model.";

  revision "2023-05-24" {
    description
      "Added OSPF authentication key-chain";
  }
  revision "2022-11-07" {
    description
      "Added auto-cost reference-bandwidth";
  }
  revision "2022-05-28" {
    description
      "Added VRF-Lite capability";
  }
  revision "2022-03-11" {
    description
      "Added default-information originate";
  }
  revision "2021-11-29" {
    description
      "Added stub area options";
  }
  revision "2021-11-18" {
    description
      "Initial revision";
  }
  augment /ncs:devices/ncs:device/mdd:openconfig/oc-netinst:network-instances/oc-netinst:network-instance/oc-netinst:protocols/oc-netinst:protocol/oc-netinst:ospfv2/oc-netinst:global/oc-netinst:config {
    when "../../../oc-netinst:identifier = 'oc-pol-types:OSPF'";
    container default-information-originate {
      container config {
        leaf enabled {
          type boolean;
          description
            "XE - Enables default routes to be injected into the OSPF routing protocol.";
        }
        leaf always {
          type boolean;
          description
            "XE - Enables default-route injection regardless if default route is present in the routing table.";
        }
        leaf metric {
          type uint64 {
            range "0..16777214";
          }
          description
            "XE - Sets the metric for the injected default-route.";
        }
        leaf metric-type {
          type uint8 {
            range "1..2";
          }
          description
            "XE - Sets the OSPF metric-type for the injected default-route.";
        }
        leaf route-map {
          type leafref {
            path "/ncs:devices/ncs:device/mdd:openconfig/oc-rpol:routing-policy/oc-rpol:policy-definitions/" +
              "oc-rpol:policy-definition/oc-rpol:name";
            }
          description
            "XE - Enables conditional default-route injection.";
        }
      }
    }
    leaf capability-vrf-lite {
      type boolean;
      description
        "XE - For PE routers, disable down-bit and domain tag checks to enable passing OSPF routes from MPLS backbone to CE routers.";
    }
  }
  augment /ncs:devices/ncs:device/mdd:openconfig/oc-netinst:network-instances/oc-netinst:network-instance/oc-netinst:protocols/oc-netinst:protocol/oc-netinst:ospfv2/oc-netinst:global/oc-netinst:timers/oc-netinst:spf/oc-netinst:config {
    when "../../../../../oc-netinst:identifier = 'oc-pol-types:OSPF'";
    leaf hold-time {
      type uint16;
      description
        "XE - Minimum hold time between two consecutive SPF calculations, in milliseconds. Range is from 1 to 600000. In OSPF for IPv6, the default value is 10,000.";
    }
  }
  augment /ncs:devices/ncs:device/mdd:openconfig/oc-netinst:network-instances/oc-netinst:network-instance/oc-netinst:protocols/oc-netinst:protocol/oc-netinst:ospfv2/oc-netinst:global/oc-netinst:timers/oc-netinst:lsa-generation/oc-netinst:config {
    when "../../../../../oc-netinst:identifier = 'oc-pol-types:OSPF'";
    leaf hold-time {
      type uint16;
      description
        "XE - Incremental time in milliseconds. This value is used to calculate the subsequent rate limiting times for LSA generation. The range is 1 to 600,000 milliseconds. The default value is 5000 milliseconds.";
    }
  }
  augment /ncs:devices/ncs:device/mdd:openconfig/oc-netinst:network-instances/oc-netinst:network-instance/oc-netinst:protocols/oc-netinst:protocol/oc-netinst:ospfv2/oc-netinst:areas/oc-netinst:area {
    when "../../../oc-netinst:identifier = 'oc-pol-types:OSPF'";
    container stub-options {
      container stub {
        container config {
          leaf enabled {
            type boolean;
            description
              "Deny LSA types 4 and 5";
          }
          leaf default-information-originate {
            type boolean;
            description
              "ABR injects a default route into the area";
          }
        }
      }
      container totally-stubby {
        container config {
          leaf enabled {
            type boolean;
            description
              "Deny LSA types 3, 4, and 5";
          }
          leaf default-information-originate {
            type boolean;
            description
              "ABR injects a default route into the area";
          }
        }
      }
      container nssa {
        container config {
          leaf enabled {
            type boolean;
            description
              "Configure area as nssa";
          }
          leaf default-information-originate {
            type boolean;
            description
              "ABR injects a default route into the area";
          }
          leaf no-summary {
            type boolean;
            description
              "do not send LSA Type 3 into nssa";
          }
        }
      }
    }
  }
  augment /ncs:devices/ncs:device/mdd:openconfig/oc-netinst:network-instances/oc-netinst:network-instance/oc-netinst:protocols/oc-netinst:protocol/oc-netinst:ospfv2/oc-netinst:global/oc-netinst:config {
    when "../../../oc-netinst:identifier = 'oc-pol-types:OSPF'";
    leaf auto-cost-ref-bandwidth {
      type uint32;
      description
        "XE - Auto cost reference bandwidth. This value affects the calculation used to determine the metric.";
    }
  }
  augment /ncs:devices/ncs:device/mdd:openconfig/oc-netinst:network-instances/oc-netinst:network-instance/oc-netinst:protocols/oc-netinst:protocol/oc-netinst:ospfv2/oc-netinst:areas/oc-netinst:area/oc-netinst:interfaces/oc-netinst:interface {
    when "../../../../../oc-netinst:identifier = 'oc-pol-types:OSPF'";
    container authentication {
      description
        "Enclosing container for OSPF Authentication";
      container config {
        leaf authentication-type {
          type enumeration {
            enum UNCONFIGURED {
              description
                "This is also called Type 0 but is not specifically null.";
            }
            enum NULL {
              description
                "This is also called Type 0 and it means no authentication information is included in the packet header.";
            }
            enum SIMPLE {
              description
                "This is also called Type 1 and it uses simple clear-text passwords.";
            }
            enum KEY-CHAIN {
              description
                "This uses a key-chain for cryptographic authentication keys.";
            }
            enum MD5 {
              description
                "This is also called Type 2 and it uses MD5 cryptographic passwords.";
            }
          }
        }
        leaf simple-password {
          when "../authentication-type = 'SIMPLE'";
          type string;
          description
            "This is a plain text authentication password.";
        }
        leaf key-chain {
          when "../authentication-type = 'KEY-CHAIN'";
          description
            "Use a key-chain for cryptographic authentication keys.";
          type leafref {
            path "/ncs:devices/ncs:device/mdd:openconfig/oc-sys:system/oc-system-ext:services/oc-system-ext:key-chains/oc-system-ext:key-chain/oc-system-ext:name";
          }
        }
      }
      container md5-authentication-keys {
        list md5-authentication-key {
          when "../../config/authentication-type = 'MD5'";
          key "key-id";
          description
            "List of authentication keys, keyed by key-id";
          leaf key-id {
            type leafref {
              path "../config/key-id";
            }
            description
              "References the configured message digest key id";
          }
          container config {
            description
              "Configuration data for the authentication key-id";
            leaf key-id {
              type uint8;
              description
                "Enables message digest key id for OSPF authentication.";
            }
            leaf key {
              type string;
              description
                "Key for OSPF authentication";
            }
          }
        }
      }
    }
  }
}
