module openconfig-routing-policy-ext{

  yang-version "1.1";

  // namespace
  namespace "http://cisco.com/openconfig-routing-policy-ext";

  prefix "oc-routing-policy-ext";

  import tailf-ncs { prefix ncs; }
  import tailf-common { prefix tailf; }
  import mdd { prefix mdd; }
  import openconfig-routing-policy { prefix oc-rpol; }
  import openconfig-extensions { prefix oc-ext; }
  import openconfig-acl { prefix oc-acl; }
  import openconfig-bgp-policy { prefix oc-bgp-pol; }


  // meta
  organization "Cisco";

  contact
    "www.cisco.com";

  description
    "Augmentation to openconfig routing-policy model.";

  revision "2023-04-11" {
    description
      "Updated to include policy_action extension";
  }
  revision "2021-10-15" {
    description
      "Initial revision";
  }

  typedef policy_action-type {
    type enumeration {
      enum PERMIT_ROUTE {
        description
          "Policy to permit the route";
      }
      enum DENY_ROUTE {
        description
          "Policy to deny the route";
      }
    }
  }

  augment /ncs:devices/ncs:device/mdd:openconfig/oc-rpol:routing-policy/oc-rpol:defined-sets/oc-rpol:prefix-sets/oc-rpol:prefix-set/oc-rpol:prefixes/oc-rpol:prefix/oc-rpol:config {
    leaf seq {
      type uint16;
      tailf:info "ios: prefix-list statement sequence number";
      description
        "Sets a sequence number for prefix-list statements.";
    }
    leaf policy_action {
      type policy_action-type;
      tailf:info "ios: prefix-list statement permit/deny action";
      description
        "Enables permit/deny for prefix-list statements.";
    }
  }
  augment /ncs:devices/ncs:device/mdd:openconfig/oc-rpol:routing-policy/oc-rpol:policy-definitions/oc-rpol:policy-definition/oc-rpol:statements/oc-rpol:statement/oc-rpol:conditions {
    container match-acl-ipv4-set {
      container config {
        leaf acl-set {
          type leafref {
            path "../../../../../../../../../oc-acl:acl/oc-acl:acl-sets/oc-acl:acl-set/oc-acl:config/oc-acl:name";
          }
        }
      }
    }
  }
  augment /ncs:devices/ncs:device/mdd:openconfig/oc-rpol:routing-policy/oc-rpol:policy-definitions/oc-rpol:policy-definition/oc-rpol:statements/oc-rpol:statement/oc-rpol:actions/oc-bgp-pol:bgp-actions/oc-bgp-pol:config {
    leaf set-weight {
          type uint16;
          description
            "The route with the highest weight will be chosen as the preferred route when multiple routes are available to a particular network.";
    }
  }
}
