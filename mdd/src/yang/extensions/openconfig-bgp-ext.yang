module openconfig-bgp-ext{

  yang-version "1.1";

  // namespace
  namespace "http://cisco.com/openconfig-bgp-ext";

  prefix "oc-bgp-ext";

  import tailf-ncs { prefix ncs; }
  import tailf-common { prefix tailf; }
  import mdd { prefix mdd; }
  import openconfig-network-instance { prefix "oc-netinst"; }
  import openconfig-extensions { prefix oc-ext; }
  import openconfig-system { prefix oc-sys; }
  import openconfig-system-ext { prefix oc-system-ext; }


  // meta
  organization "Cisco";

  contact
    "www.cisco.com";

  description
    "Augmentation to openconfig bgp model.";

  revision "2023-07-19" {
    description
      "Added auth-password encryption";
  }
  revision "2023-05-25" {
    description
      "Added TCP-AO Authentication";
  }
  revision "2022-02-17" {
    description
      "Added log-neighbor-changes";
  }
  revision "2022-02-10" {
    description
      "Initial revision";
  }

  augment /ncs:devices/ncs:device/mdd:openconfig/oc-netinst:network-instances/oc-netinst:network-instance/oc-netinst:protocols/oc-netinst:protocol/oc-netinst:bgp/oc-netinst:neighbors/oc-netinst:neighbor/oc-netinst:config {
    when "../../../../oc-netinst:identifier = 'oc-pol-types:BGP'";
    leaf ttl-security {
        type uint8 {
            range "1..254";
        }
        description
          "XE - Protects the eBGP peering session by comparing the value in the TTL field of received IP packets against a hop count that is configured locally for each eBGP peering session";
    }
  }
  augment /ncs:devices/ncs:device/mdd:openconfig/oc-netinst:network-instances/oc-netinst:network-instance/oc-netinst:protocols/oc-netinst:protocol/oc-netinst:bgp/oc-netinst:global/oc-netinst:config {
    when "../../../oc-netinst:identifier = 'oc-pol-types:BGP'";
    leaf log-neighbor-changes {
      type boolean;
      description
        "Enables logging of neighbor changes.";
    }
  }
  augment /ncs:devices/ncs:device/mdd:openconfig/oc-netinst:network-instances/oc-netinst:network-instance/oc-netinst:protocols/oc-netinst:protocol/oc-netinst:bgp/oc-netinst:neighbors/oc-netinst:neighbor/oc-netinst:config {
    when "../../../../oc-netinst:identifier = 'oc-pol-types:BGP'";
    leaf tcpao-keychain {
      type string;
      description
        "Uses a TCP-AO key-chain.";
    }
  }
  augment /ncs:devices/ncs:device/mdd:openconfig/oc-netinst:network-instances/oc-netinst:network-instance/oc-netinst:protocols/oc-netinst:protocol/oc-netinst:bgp/oc-netinst:peer-groups/oc-netinst:peer-group/oc-netinst:config {
    when "../../../../oc-netinst:identifier = 'oc-pol-types:BGP'";
    leaf tcpao-keychain {
      type string;
      description
        "Uses a TCP-AO key-chain.";
    }
  }
  augment /ncs:devices/ncs:device/mdd:openconfig/oc-netinst:network-instances/oc-netinst:network-instance/oc-netinst:protocols/oc-netinst:protocol/oc-netinst:bgp/oc-netinst:neighbors/oc-netinst:neighbor/oc-netinst:config {
    when "../../../../oc-netinst:identifier = 'oc-pol-types:BGP'";
    leaf password-encryption {
      type enumeration {
        enum CLEARTEXT;
        enum ENCRYPTED;
      }
      description
        "Enables neighbor auth-password encryption.";
    }
  }
  augment /ncs:devices/ncs:device/mdd:openconfig/oc-netinst:network-instances/oc-netinst:network-instance/oc-netinst:protocols/oc-netinst:protocol/oc-netinst:bgp/oc-netinst:peer-groups/oc-netinst:peer-group/oc-netinst:config {
    when "../../../../oc-netinst:identifier = 'oc-pol-types:BGP'";
    leaf password-encryption {
      type enumeration {
        enum CLEARTEXT;
        enum ENCRYPTED;
      }
      description
        "Enables peer-group auth-password encryption.";
    }
  }
}
