module openconfig-system-ext{

  yang-version "1.1";

  // namespace
  namespace "http://cisco.com/openconfig-system-ext";

  prefix "oc-system-ext";

  import openconfig-system { prefix oc-sys; }
  import openconfig-interfaces { prefix oc-if; }
  import tailf-ncs { prefix ncs; }
  import tailf-common { prefix tailf; }
  import mdd { prefix mdd; }
  import openconfig-network-instance { prefix "oc-netinst"; }
  import openconfig-extensions { prefix oc-ext; }
  import openconfig-inet-types { prefix oc-inet; }
  import openconfig-system-logging { prefix oc-log; }
  import openconfig-aaa-types { prefix oc-aaa-types; }
  import openconfig-vlan-types { prefix oc-vlan-types; }

  // Include NAT submodule.
  include system-ext-sub-nat;

  // meta
  organization "Cisco";

  contact
    "www.cisco.com";

  description
    "Augmentation to openconfig system model.";

  revision "2023-07-11" {
    description
      "Added Dynamic ARP inspection support";
  }
  revision "2023-07-11" {
    description
      "Added DHCP Snooping support";
  }
  revision "2023-07-10" {
    description
      "Added UDLD support";
  }
  revision "2023-05-18" {
    description
      "Added key chain support";
  }
  revision "2022-09-26" {
    description
      "organized to OC standard";
  }
  revision "2022-09-22" {
    description
      "Added no ip domain lookup";
  }
  revision "2021-08-08" {
    description
      "Initial revision";
  }
  identity IP_OPTIONS {
    description
      "Drop or ignore ip options";
  }
  identity ENABLE {
    base IP_OPTIONS;
    description
      "Process IP options packets that are sent to the router";
  }
  identity DROP {
    base IP_OPTIONS;
    description
      "Drops IP options packets that are sent to the router";
  }
   identity IGNORE {
    base IP_OPTIONS;
    description
      "Ignores IP options packets that are sent to the router";
  }
  identity CIPHERSUITE_TYPE {
    description
      "Base identity to define ciphersuite types";
  }
  identity aes-128-cbc-sha {
    base CIPHERSUITE_TYPE;
    description
      "Encryption type tls_rsa_with_aes_cbc_128_sha ciphersuite.";
  }
  identity aes-256-cbc-sha {
    base CIPHERSUITE_TYPE;
    description
      "Encryption type tls_rsa_with_aes_cbc_256_sha ciphersuite.";
  }
  identity dhe-aes-cbc-sha2 {
    base CIPHERSUITE_TYPE;
    description
      "Encryption type tls_dhe_rsa_with_aes_cbc_sha2(TLS1.2 & above) ciphersuite.";
  }
  identity dhe-aes-gcm-sha2 {
    base CIPHERSUITE_TYPE;
    description
      " Encryption type tls_dhe_rsa_with_aes_gcm_sha2(TLS1.2 & above) ciphersuite.";
  }
  identity ecdhe-ecdsa-aes-gcm-sha2 {
    base CIPHERSUITE_TYPE;
    description
      "ncryption type tls_ecdhe_ecdsa_aes_gcm_sha2  (TLS1.2 & above) SuiteB ciphersuite.";
  }
  identity ecdhe-rsa-aes-128-cbc-sha {
    base CIPHERSUITE_TYPE;
    description
      "Encryption type tls_ecdhe_rsa_with_aes_128_cbc_sha ciphersuite.";
  }
  identity ecdhe-rsa-aes-cbc-sha2 {
    base CIPHERSUITE_TYPE;
    description
      "Encryption type tls_ecdhe_rsa_aes_cbc_sha2(TLS1.2 & above) ciphersuite.";
  }
  identity ecdhe-rsa-aes-gcm-sha2 {
    base CIPHERSUITE_TYPE;
    description
      "Encryption type tls_ecdhe_rsa_aes_gcm_sha2(TLS1.2  & above) ciphersuite.";
  }
  identity rsa-aes-cbc-sha2 {
    base CIPHERSUITE_TYPE;
    description
      "Encryption type tls_rsa_with_aes_cbc_sha2(TLS1.2 & above) ciphersuite.";
  }
  identity rsa-aes-gcm-sha2 {
    base CIPHERSUITE_TYPE;
    description
      "Encryption type tls_rsa_with_aes_gcm_sha2(TLS1.2 & above) ciphersuite.";
  }
  identity ENCRYPTION_ALGORITHM {
    description
      "Base identity to define encryption algorithms";
  }
  identity triple-des-cbc {
    base ENCRYPTION_ALGORITHM;
    description
      "Encryption algorithm Three-key 3DES in CBC mode.";
  }
  identity aes128-cbc {
    base ENCRYPTION_ALGORITHM;
    description
      "Encryption algorithm AES with 128-bit key in CBC mode.";
  }
  identity aes128-ctr {
    base ENCRYPTION_ALGORITHM;
    description
      "Encryption algorithm AES with 128-bit key in CTR mode.";
  }
  identity aes192-cbc {
    base ENCRYPTION_ALGORITHM;
    description
      "Encryption algorithm AES with 192-bit key in CBC mode.";
  }
  identity aes192-ctr {
    base ENCRYPTION_ALGORITHM;
    description
      "Encryption algorithm AES with 192-bit key in CTR mode.";
  }
  identity aes256-cbc {
    base ENCRYPTION_ALGORITHM;
    description
      "Encryption algorithm AES with 256-bit key in CBC mode.";
  }
  identity aes256-ctr {
    base ENCRYPTION_ALGORITHM;
    description
      "Encryption algorithm AES with 256-bit key in CTR mode.";
  }
  identity aes256-gcm {
    base ENCRYPTION_ALGORITHM;
    description
      "Encryption algorithm AES with 256-bit key GCM mode.";
  }
  identity MAC_ALGORITHM {
    description
      "MAC algorithms advertised to other party";
  }
  identity hmac-sha1 {
    base MAC_ALGORITHM;
    description
      "HMAC-SHA1 (digest length = key length = 160 bits).";
  }
  identity hmac-sha1-96 {
    base MAC_ALGORITHM;
    description
      "HMAC-SHA1-96 (digest length = 96 bits, key length = 160 bits).";
  }
  identity hmac-sha2-256 {
    base MAC_ALGORITHM;
    description
      "HMAC-SHA2-256 (digest length = 256 bits, key length = 256 bits).";
  }
  identity hmac-sha2-512 {
    base MAC_ALGORITHM;
    description
      "HMAC-SHA2-512 (digest length = 512 bits, key length = 512 bits).";
  }

  // Hour&minute&second type
  typedef hhmmss-type {
    type string {
      pattern "([0-1]?[0-9]|2[0-4]):([0-5][0-9])(:[0-5][0-9])";
    }
  }

  // Month type
  typedef month-type {
    type enumeration {
      enum Jan;
      enum Feb;
      enum Mar;
      enum Apr;
      enum May;
      enum Jun;
      enum Jul;
      enum Aug;
      enum Sep;
      enum Oct;
      enum Nov;
      enum Dec;
    }
  }

  // Key Chain lifetime
  grouping lifetime-grouping {
    leaf start-time {
      type hhmmss-type;
      description "hh:mm;;Time to start (hh:mm)";
    }
    leaf start-month {
      type month-type;
      description "MONTH;;Month of the year to start";
    }
    leaf start-date {
      type uint8 {
        range "1..31";
      }
      description "<1-31>;;Day of the month to start";
    }
    leaf start-year {
      type uint16 {
        range "1993..2035";
      }
      description "<1993-2035>;;Year to start";
    }
    leaf duration {
      type uint32 {
        range "1..2147483646";
      }
      description "Set key lifetime duration in seconds. <1-2147483646>";
    }
    leaf infinite {
      type boolean;
      //default false;
      description "Never expires";
    }
    leaf stop-time {
      type hhmmss-type;
      description "hh:mm;;Time to stop (hh:mm)";
    }
    leaf stop-month {
      type month-type;
      description "MONTH;;Month of the year to stop";
    }
    leaf stop-date {
      type uint8 {
        range "1..31";
      }
      description "<1-31>;;Day of the month to stop";
    }
    leaf stop-year {
      type uint16 {
        range "1993..2035";
      }
      description "<1993-2035>;;Year to stop";
    }
  }

  augment /ncs:devices/ncs:device/mdd:openconfig/oc-sys:system {
    container timestamps {
      description
        "Configure logging and debugging time-stamps messages.";
      container logging {
        description
          "Configure logging time-stamps messages.";
         container config {
          leaf enabled {
            type boolean;
            description
              "Enables timestamps for logging.";
           }
          leaf datetime {
            type boolean;
            description
              "Time stamp with the date and time.";
           }
           leaf localtime {
            type boolean;
            description
              "Time stamp relative to the local time zone.";
           }
           leaf uptime {
            type boolean;
            description
              "Time stamp with time since the system was rebooted.";
           }
         }
       }
      container debugging {
        description
          "Configure debugging time-stamps messages.";
        container config {
          leaf enabled {
            type boolean;
            description
              "Enables timestamps for debugging.";
           }
          leaf datetime {
            type boolean;
            description
              "Time stamp with the date and time.";
           }
           leaf localtime {
            type boolean;
            description
              "Time stamp relative to the local time zone.";
           }
           leaf msec {
            type boolean;
            description
              "Include milliseconds in the date and time stamp.";
           }
           leaf uptime {
            type boolean;
            description
              "Time stamp with time since the system was rebooted.";
           }
         }
       }
     }
    container services {
      description
        "Minor network device services";
      container config {
        leaf ip-domain-lookup {
            type boolean;
            //default true;
            description
              "Disable or enable ip domain-lookup.";
        }
        leaf ip-gratuitous-arps {
          type boolean;
          description
            "Enable the transmission of gratuitous Address Resolution Protocol (ARP) messages.";
        }
        leaf archive-logging {
          type boolean;
          description
            "Enable the config logger.";
        }
        leaf ip-bootp-server {
          type boolean;
          description
            "Config BOOTP services.";
        }
        leaf ip-dns-server {
          type boolean;
          description
            "Configure DNS server for a zone.";
        }
        leaf ip-identd {
          type boolean;
          description
            "Configure Ident server.";
        }
        leaf ip-rcmd-rcp-enable {
          type boolean;
          description
            "Enable server side of RCP.";
        }
        leaf ip-rcmd-rsh-enable {
          type boolean;
          description
            "Enable server side of RSH.";
        }
        leaf finger {
          type boolean;
          //default false;
          description
            "Configure a system to accept Finger protocol requests.";
        }
        leaf service-config {
          type boolean;
          description
            "Enables TFTP load config files.";
        }
        leaf service-tcp-small-servers {
          type boolean;
          description
            "Enables small TCP servers such as the ECHO.";
        }
        leaf service-udp-small-servers {
          type boolean;
          description
            "Enables small User Datagram Protocol (UDP) servers such as the ECHO.";
        }
        leaf service-pad {
          type boolean;
          description
            "Enable PAD commands.";
        }
        leaf service-password-encryption {
          type boolean;
          description
            "Encrypt system passwords.";
        }
      }
      container key-chains {
        list key-chain {
          key "name";
          leaf name {
            type string;
          }
          leaf type {
            type enumeration {
              enum NOT_APPLICABLE;
              enum MACSEC;
              enum TCP;
            }
           //default NOT_APPLICABLE;
          }
          list keys {
            key "id";
            leaf id {
              type leafref {
                path "../config/id";
              }
            }
            container config {
              leaf id {
                type uint32 {
                  range "0 .. 2147483647";
                }
                description
                  "Key identifier.";
              }
              leaf key-string {
                type string;
                description
                  "Set key string";
              }
              leaf cryptographic-algorithm {
                when "../../../type = 'NOT_APPLICABLE'" {
                  description
                    "Set cryptographic authentication algorithm";
                }
                type enumeration {
                  enum hmac-sha-1 {
                    description "HMAC-SHA-1 authentication algorithm";
                  }
                  enum hmac-sha-256 {
                    description "HMAC-SHA-256 authentication algorithm";
                  }
                  enum hmac-sha-384 {
                    description "HMAC-SHA-384 authentication algorithm";
                  }
                  enum hmac-sha-512 {
                    description "HMAC-SHA-512 authentication algorithm";
                  }
                  enum md5 {
                   description "MD5 authentication algorithm";
                  }
                }
              }
              leaf cryptographic-algorithm-tcp {
                when "../../../type = 'TCP'" {
                  description
                    "Set cryptographic authentication algorithm for TCP key-chain";
                }
                type enumeration {
                  enum aes-128-cmac {
                    description "AES-128-CMAC authentication algorithm";
                  }
                  enum hmac-sha-1 {
                    description "HMAC-SHA-1 authentication algorithm";
                  }
                  enum hmac-sha-256 {
                    description "HMAC-SHA-256 authentication algorithm";
                  }
                }
              }
              leaf send-id {
                when "../../../type = 'TCP'" {
                  description
                    "Configure a send id";
                }
                type uint8 {
                  range "0..255";
                }
              }
              leaf recv-id {
                when "../../../type = 'TCP'" {
                  description
                    "Configure a receive id";
                }
                type uint8 {
                  range "0..255";
                }
              }
              container accept-lifetime {
                description "Set accept lifetime of key";
                choice accept-lifetime-choice {
                  case global {
                    uses lifetime-grouping;
                  }
                  container local {
                    description "Specify time in local timezone";
                    uses lifetime-grouping;
                  }
                }
              }
              container send-lifetime {
                description "Set send lifetime of key";
                choice send-lifetime-choice {
                  case global {
                    uses lifetime-grouping;
                  }
                  container local {
                    description "Specify time in local timezone";
                    uses lifetime-grouping;
                  }
                }
              }
            }
          }
        }
      }
      container object-tracking {
        list object-track {
          key "id";
          leaf id {
            type leafref {
              path "../config/id";
            }
          }
          leaf type {
            type enumeration {
              enum INTERFACE;
            }
            mandatory true;
          }
          container config {
            leaf id {
              type uint16 {
                range "0 .. 1000";
              }
            }
            leaf track-interface {
              type leafref {
                path "/ncs:devices/ncs:device/mdd:openconfig/oc-if:interfaces/oc-if:interface/oc-if:name";
              }
              mandatory true;
            }
            leaf track-parameter {
              type enumeration {
                enum IP-ROUTING;
                enum LINE-PROTOCOL;
              }
              mandatory true;
            }
          }
        }
        container config {
          container timer {
            leaf interface-timer {
              type uint16 {
                range "0 .. 3000";
              }
              units "seconds";
            }
          }
        }
      }
      container boot-network  {
        description
          "boot-network configurations";
        container config {
          leaf bootnetwork-enabled {
            type enumeration {
              enum MANUAL_CONFIG;
              enum DISABLED;
            }
            description
              "Configure a system to boot from network-wide config file.";
          }
        }
      }
      container udld  {
        description
          "Configure global UDLD settings.";
        container config {
          leaf udld {
            type enumeration {
              enum ENABLED;
              enum AGGRESSIVE;
              enum DISABLED;
            }
            //default DISABLED;
            description
              "Enable (or enable in aggressive mode) UDLD protocol on fiber ports except where locally configured.";
          }
          leaf message-time {
            when "../udld = 'ENABLED' or ../udld = 'AGGRESSIVE'" {
              description
                "Time in seconds between sending of messages in steady state.";
            }
            type uint8 {
              range "0 .. 90";
            }
          }
          leaf recovery {
            when "../udld = 'ENABLED' or ../udld = 'AGGRESSIVE'" {
              description
                "Enable timer to recover from udld error disable state.";
            }
            type enumeration {
              enum ENABLED;
              enum DISABLED;
            }
            //default DISABLED;
          }
          leaf recovery-interval {
            when "../recovery = 'ENABLED'" {
              description
                "Error disable recovery timer-interval value (sec).";
            }
            type uint32 {
              range "30 .. 86400";
            }
          }
        }
      }
      container dhcp-snooping {
        description
          "Configure DHCP Snooping settings.";
        container global-config {
          container config {
            description
              "Global configuration parameters relating to DHCP Snooping";
            leaf enable {
              type enumeration {
                enum ENABLED;
                enum DISABLED;
              }
              //default DISABLED;
              description
                "Enable DHCP Snooping globally.";
            }
          }
        }
        list vlans {
          key "vlan-id";
          description
            "List of the vlans";
          leaf vlan-id {
            type leafref {
              path "../config/vlan-id";
            }
            description
            "Reference to the list key";
          }
          container config {
            description
              "Configuration parameters relating to DHCP Snooping";
            leaf vlan-id {
              type oc-vlan-types:vlan-id;
              description
                "VLAN ID";
            }
            leaf enable {
              type enumeration {
                enum ENABLED;
                enum DISABLED;
              }
              default DISABLED;
              description
                "Enable DHCP Snooping vlan for VLAN ID.";
            }
          }
        }
      }
      container dynamic-arp-inspection {
        description
          "Configure DAI settings.";
        list vlans {
          key "vlan-id";
          description
            "List of the vlans";
          leaf vlan-id {
            type leafref {
              path "../config/vlan-id";
            }
            description
            "Reference to the list key";
          }
          container config {
            description
              "Configuration parameters relating to dynamic ARP inspection";
            leaf vlan-id {
              type oc-vlan-types:vlan-id;
              description
                "VLAN ID";
            }
            leaf enable {
              type enumeration {
                enum ENABLED;
                enum DISABLED;
               }
               default DISABLED;
               description
                 "Enable dynamic ARP inspection for VLAN ID.";
            }
          }
        }
      }
      container login-security-policy {
        description
          "Login security policy services";
        container config {
          leaf on-success {
            type boolean;
            description
              "Enables logging for successful login attempt.";
          }
          leaf on-failure {
            type boolean;
            description
              "Enables logging for failed login attempt.";
          }
        }
        container block-for {
          description
            "Login block-for security policy services";
          container config {
            leaf seconds {
              type uint16;
              description
                "Set quiet-mode active time period.";
            }
            leaf attempts {
              type uint16;
              description
                "Set max number of fail attempts.";
            }
            leaf within {
              type uint16;
              description
                "Watch period for fail attempts.";
            }
          }
        }
      }
      container http {
        description
          "HTTP server configurations";
        container config {
          leaf http-enabled {
              type boolean;
              //default false;
              description
                "Enable HTTP Server.";
          }
          leaf https-enabled {
              type boolean;
              //default false;
              description
                "Enable HTTPS Server.";
          }
          leaf ip-http-max-connections {
            type uint16;
            tailf:info "ios: ip http max connections";
            description
              "Sets the maximum number of concurrent connections allowed for the HTTP server.";
          }
          leaf-list ip-http-secure-ciphersuite {
            type identityref {
              base oc-system-ext:CIPHERSUITE_TYPE;
            }
            tailf:info "ios: ip http secure-ciphersuite";
            description
              "Specifies the CipherSuites that should be used by the secure HTTP server when negotiating a connection with a remote client.";
          }
        }
        container ip-http-timeout-policy {
          description
            "Sets the parameters for closing connections to the local HTTP server.";
          container idle {
            description
              "Specifies the maximum number of seconds that a connection will be kept open if no data is received or response data cannot be sent out.";
            container config {
              leaf connection {
                type uint16 {
                  range "0 .. 600";
                }
                description
                  "Connection idle time-out value in seconds.";
              }
              leaf life {
                type uint32 {
                  range "0 .. 86400";
                }
                description
                  "Specifies the maximum number of seconds that a connection will be kept open from the time the connection is established.";
              }
              leaf requests {
                type uint32 {
                  range "0 .. 86400";
                }
                description
                  "Specifies that a maximum limit is set on the number of requests processed on a persistent connection before it is closed.";
              }
            }
          }
        }
      }
      uses config-ip-nat-grouping;
    }
  }
  augment /ncs:devices/ncs:device/mdd:openconfig/oc-sys:system/oc-sys:config {
    leaf console-exec-timeout-seconds {
      type uint16 {
        range "0 .. 35791";
      }
      description
        "Configure the inactive session timeout on the console port in seconds.";
    }
    leaf ip-options {
      type identityref {
        base IP_OPTIONS;
      }
      description
        "Drops or ignores IP options packets that are sent to the router.";
    }
    leaf enable-secret {
      type string;
      description
        "Sets a local password to control access to various privilege levels.
        At this time, only encryption-type 0 is supported.";
    }
  }
  augment /ncs:devices/ncs:device/mdd:openconfig/oc-sys:system/oc-sys:ntp/oc-sys:config {
    leaf ntp-enable-logging {
      type boolean;
      description
        "Enables Network Time Protocol (NTP) message logging.";
    }
  }
  augment /ncs:devices/ncs:device/mdd:openconfig/oc-sys:system/oc-sys:ntp/oc-sys:servers/oc-sys:server/oc-sys:config {
    leaf ntp-auth-key-id {
      type uint16;
      description
        "Links to authentication key in oc-sys:system/ntp/ntp-keys";
    }
    leaf ntp-source-address {
      type oc-inet:ip-address;
      description
        "Source address to use on outgoing NTP packets";
    }
    leaf ntp-use-vrf {
      type leafref {
        path "/ncs:devices/ncs:device/mdd:openconfig/oc-netinst:network-instances/oc-netinst:network-instance/oc-netinst:name";
      }
      description
        "VRF for communication with NTP servers.";
    }
  }
  augment /ncs:devices/ncs:device/mdd:openconfig/oc-sys:system/oc-sys:ssh-server {
    container algorithm {
      container config {
        description "Specifies the different algorithms used in SSH.";
        leaf-list encryption {
          type identityref {
            base oc-system-ext:ENCRYPTION_ALGORITHM;
          }
          tailf:info "ios: ip ssh server algorithm encryption";
          description "Specifies the Encryption algorithms advertised to other party.";
        }
        leaf-list mac {
          type identityref {
            base oc-system-ext:MAC_ALGORITHM;
          }
          tailf:info "ios: ip ssh server algorithm mac";
          description "Specifies the MAC algorithms advertised to other party.";
        }
      }
    }
  }
  augment /ncs:devices/ncs:device/mdd:openconfig/oc-sys:system/oc-sys:ssh-server/oc-sys:config {
    leaf absolute-timeout-minutes {
      type uint16 {
        range "0 .. 35791";
      }
      description
        "The absolute timeout for line disconnection in minutes.";
    }
    leaf ssh-source-interface {
      type leafref {
        path "/ncs:devices/ncs:device/mdd:openconfig/oc-if:interfaces/oc-if:interface/oc-if:name";
      }
      description
        "Secure Shell (SSH) control parameter to set the time interval that the router waits for the SSH client to respond.
        In IOS, seconds from 1-120.";
    }
    leaf ssh-timeout {
      type uint16 {
        range "0 .. 120";
      }
      description
        "Secure Shell (SSH) control parameter to set the time interval that the router waits for the SSH client to respond.
        In IOS, seconds from 1-120.";
    }
  }
  augment /ncs:devices/ncs:device/mdd:openconfig/oc-sys:system/oc-sys:logging/oc-sys:remote-servers/oc-sys:remote-server/oc-sys:config {
    leaf use-vrf {
      type leafref {
        path "/ncs:devices/ncs:device/mdd:openconfig/oc-netinst:network-instances/oc-netinst:network-instance/oc-netinst:name";
      }
      description
        "VRF from which to reach the logging servers. '' for no VRF.";
    }
  }
  augment /ncs:devices/ncs:device/mdd:openconfig/oc-sys:system/oc-sys:logging/oc-sys:console/oc-sys:config {
      leaf enabled {
        type boolean;
        description
          "Enables logging messages output to console.";
      }
  }
  augment /ncs:devices/ncs:device/mdd:openconfig/oc-sys:system/oc-sys:logging {
    container buffered {
      container config {
        description "Specifies the logging buffer as a destination for system logging (syslog) messages.";
          leaf enabled {
            type boolean;
            description
              "Enables local buffering of logging messages.";
          }
          leaf severity {
            type oc-log:syslog-severity;
            description
              "Specifies that only messages of the given severity (or
              greater severity) for the corresonding facility are logged";
          }
          leaf buffer-size {
            type uint32 {
              range "4096 .. 2147483647";
            }
            description
              "Size of the buffer, in bytes.";
          }
      }
    }
    container terminal-monitor {
      description
        "Specifies terminal lines other than the console terminal as destinations for system logging (syslog) messages.";
      container selectors {
        description
          "Enclosing container ";
        list selector {
          key "facility severity";
          description
            "List of selectors for log messages";

          leaf facility {
            type leafref {
              path "../config/facility";
            }
            description
              "Reference to facility list key";
          }
          leaf severity {
            type leafref {
              path "../config/severity";
            }
            description
              "Reference to severity list key";
          }
          container config {
            leaf facility {
              type identityref {
                base oc-log:SYSLOG_FACILITY;
              }
              description
                "Specifies the facility, or class of messages to log";
            }
            leaf severity {
              type oc-log:syslog-severity;
              description
                "Specifies that only messages of the given severity (or
                greater severity) for the corresonding facility are logged";
            }
          }
        }
      }
    }
  }
  augment /ncs:devices/ncs:device/mdd:openconfig/oc-sys:system/oc-sys:dns/oc-sys:servers/oc-sys:server/oc-sys:config {
    leaf use-vrf {
      type leafref {
        path "/ncs:devices/ncs:device/mdd:openconfig/oc-netinst:network-instances/oc-netinst:network-instance/oc-netinst:name";
      }
      description
        "VRF from which to reach the DNS servers. '' for no VRF.";
    }
  }
  augment /ncs:devices/ncs:device/mdd:openconfig/oc-sys:system/oc-sys:aaa/oc-sys:authentication {
    container authentication-lists-login {
      container config {
        description
          "Configuration data for global authentication services";
        leaf name {
          type string;
          description
            "XE - Named authentication list";
        }
        leaf-list authentication-method {
          type union {
            type identityref {
              base oc-aaa-types:AAA_METHOD_TYPE;
            }
            type string;
          }
        }
      }
    }
  }
}
