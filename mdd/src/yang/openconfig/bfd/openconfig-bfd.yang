module openconfig-bfd {

  yang-version "1";

  // namespace
  namespace "http://openconfig.net/yang/bfd";

  prefix "oc-bfd";
  import tailf-ncs { prefix ncs; }
  import mdd { prefix mdd; }

  // import some basic types
  import openconfig-extensions { prefix "oc-ext"; }
  import openconfig-types { prefix "oc-types"; }
  import openconfig-interfaces { prefix "oc-if"; }
  import openconfig-if-types { prefix "oc-ift"; }
  import openconfig-inet-types { prefix "oc-inet"; }
  import openconfig-policy-types { prefix "oc-pol-types"; }
  import ietf-inet-types { prefix "ietf-if"; }

  // meta
  organization "OpenConfig working group";

  contact
    "OpenConfig working group
    www.openconfig.net";

  description
    "An OpenConfig model of Bi-Directional Forwarding Detection (BFD)
    configuration and operational state.";

  oc-ext:openconfig-version "0.2.4";

  revision "2022-06-28" {
    description
      "Remove reference to invalid oc-ift type check";
    reference "0.2.4";
  }

  revision "2021-06-16" {
    description
      "Remove trailing whitespace";
    reference "0.2.3";
  }

  revision "2021-03-17" {
    description
      "Remove augments from bfd module.
       Add bfd support directly on the protocols";
    reference "0.2.2";
  }

  revision "2020-05-08" {
    description
      "Ensure that when statements reference only read-write leaves
      from read-write contexts.
      Add ietf-inet-types LAG type to conditions for micro-bfd.";
    reference "0.2.1";
  }

  revision "2019-10-25" {
    description
      "Correct when statements.";
    reference "0.2.0";
  }

  revision "2019-06-02" {
    description
      "Fix detection multiplier to be 8-bit value";
    reference "0.1.1";
  }

  revision "2018-11-21" {
    description
      "Add OpenConfig module metadata extensions.";
    reference "0.1.0";
  }

  revision "2017-10-19" {
    description
      "Adopt OpenConfig types models, type corrections";
    reference "0.0.2";
  }

  revision "2016-06-24" {
    description
      "Initial revision";
    reference "0.0.1";
  }

  // OpenConfig specific extensions for module metadata.
  oc-ext:regexp-posix;
  oc-ext:catalog-organization "openconfig";
  oc-ext:origin "openconfig";

  typedef bfd-session-state {
    type enumeration {
      enum UP {
        description
          "The BFD session is perceived to be up by the system.";
      }
      enum DOWN {
        description
          "The BFD session is perceived to be down by the system.";
      }
      enum ADMIN_DOWN {
        description
          "The BFD session is administratively disabled.";
      }
      enum INIT {
        description
          "The BFD session is perceived to be initialising by the
          system.";
      }
    }
    description
      "The state of the BFD session according to the system referred
      to by the context of the leaf.";
    reference
      "RFC5880 - Bidirectional Forwarding Detection, Section
      4.1";
  }

  typedef bfd-diagnostic-code {
    type enumeration {
      enum NO_DIAGNOSTIC {
        value 0;
        description
          "No diagnostic code was specified, or the session has not
          changed state.";
      }
      enum DETECTION_TIMEOUT {
        value 1;
        description
          "The control detection time expired: no BFD packet was
          received within the required period.";
      }
      enum ECHO_FAILED {
        value 2;
        description
          "The BFD echo function failed - echo packets have not been
          received for the required period of time.";
      }
      enum FORWARDING_RESET {
        value 3;
        description
          "The forwarding plane in the local system was reset - such
          that the remote system cannot rely on the forwarding state of
          the device specifying this error code.";
      }
      enum PATH_DOWN {
        value 4;
        description
          "Signalling outside of BFD specified that the path underlying
          this session has failed.";
      }
      enum CONCATENATED_PATH_DOWN {
        value 5;
        description
          "When a BFD session runs over a series of path segments, this
          error code indicates that a subsequent path segment (i.e.,
          one in the transmit path between the source and destination
          of the session) has failed.";
      }
      enum ADMIN_DOWN {
        value 6;
        description
          "The BFD session has been administratively disabled by the
          peer.";
      }
      enum REVERSE_CONCATENATED_PATH_DOWN {
        value 7;
        description
          "In the case that a BFD session is running over a series of
          path segments, this error code indicates that a path segment
          on the reverse path (i.e., in the transmit direction from the
          destination to the source of the session) has failed.";
      }
    }
    description
      "Diagnostic codes defined by BFD. These typically indicate the
      reason for a change of session state.";
    reference
      "RFC5880 - Bidirectional Forwarding Detection, Section
      4.1";
  }


//  grouping bfd-interface-config {
//    description
//      "Top-level per-interface configuration parameters for BFD.";
//
//    leaf id {
//      type string;
//      description
//        "A unique identifier for the interface.";
//    }
//
//    leaf enabled {
//      type boolean;
//      description
//        "When this leaf is set to true then the BFD session is enabled
//        on the specified interface - if it is set to false, it is
//        administratively disabled.";
//    }
//
//    leaf local-address {
//      type oc-inet:ip-address;
//      description
//        "The source IP address to be used for BFD sessions over this
//        interface.";
//    }
//
//    leaf desired-minimum-tx-interval {
//      type uint32;
//      units microseconds;
//      description
//        "The minimum interval between transmission of BFD control
//        packets that the operator desires. This value is advertised to
//        the peer, however the actual interval used is specified by
//        taking the maximum of desired-minimum-tx-interval and the
//        value of the remote required-minimum-receive interval value.
//
//        This value is specified as an integer number of microseconds.";
//    }
//
//    leaf required-minimum-receive {
//      type uint32;
//      units microseconds;
//      description
//        "The minimum interval between received BFD control packets that
//        this system should support. This value is advertised to the
//        remote peer to indicate the maximum frequency (i.e., minimum
//        inter-packet interval) between BFD control packets that is
//        acceptable to the local system.";
//    }
//
//    // rjs: Could have required-minimum-echo-receive here, but this is
//    // generally not configurable.
//
//    leaf detection-multiplier {
//      type uint8 {
//        range "1..max";
//      }
//      description
//        "The number of packets that must be missed to declare this
//        session as down. The detection interval for the BFD session
//        is calculated by multiplying the value of the negotiated
//        transmission interval by this value.";
//    }
//
//    leaf enable-per-member-link {
//      type boolean;
//      //default false;
//      description
//        "When this leaf is set to true - BFD will be enabled on
//        each member interface of the aggregated Ethernet bundle.";
//    }
//  }


//  grouping bfd-interface-microbfd-config {
//    description
//      "Configuration parameters for a microBFD session on an
//      interface.";
//
//    leaf local-address {
//      type oc-inet:ip-address;
//      description
//        "The local IP address used by the system for the micro-BFD session
//        specified.";
//    }
//
//    leaf remote-address {
//      type oc-inet:ip-address;
//      description
//        "The remote IP destination that should be used by the system for
//        the micro-BFD session specified.";
//    }
//
//    leaf member-interface {
//      type leafref {
//        path "/ncs:devices/ncs:device/mdd:openconfig/oc-if:interfaces/" +
//          "oc-if:interface/oc-if:config/oc-if:name";
//      }
//      // rjs: Note that this does not restrict to only interfaces that
//      // are part of the current LAG. An implementation should return
//      // NOK if such an interface is specified.
//      description
//        "Reference to a member link of the aggregate interface being
//        described.";
//    }
//  }


//  grouping bfd-interface-microbfd-structural {
//    description
//      "Structural grouping for micro-bfd configuration and state
//      parameters.";
//
//    container micro-bfd-sessions {
//      when "/ncs:devices/ncs:device/mdd:openconfig/oc-if:interfaces/oc-if:interface" +
//          "[oc-if:name=current()/../interface-ref/config/interface]/" +
//          "oc-if:config/oc-if:type = 'oc-ift:IF_AGGREGATE' or " +
//          "/ncs:devices/ncs:device/mdd:openconfig/oc-if:interfaces/oc-if:interface" +
//          "[oc-if:name=current()/../interface-ref/config/interface]/" +
//          "oc-if:config/oc-if:type = 'ietf-if:ieee8023adLag'" {
//        description
//          "Include per-member link BFD only when the type of
//          interface is a link aggregate.";
//      }
//
//      description
//        "Parameters relating to micro-BFD sessions associated
//        with the interface.";
//
//      list micro-bfd-session {
//        key "member-interface";
//
//        description
//          "This list contains configuration and state parameters
//          relating to micro-BFD session.";
//        reference
//          "RFC7130 - Bidirectional Forwarding Detection (BFD)
//          on Link Aggregation Group (LAG) Interfaces.";
//
//
//        leaf member-interface {
//          type leafref {
//            path "../config/member-interface";
//          }
//          description
//            "A reference to the member interface of the link
//            aggregate.";
//        }
//
//        container config {
//          description
//            "Configuration parameters for the micro-BFD session.";
//          uses bfd-interface-microbfd-config;
//        }
//      }
//    }
//  }

//  grouping bfd-top {
//    description
//      "Structural grouping for Bidirectional Forwarding Detection (BFD).";
//
//    container bfd {
//      description
//        "Configuration and operational state parameters for BFD.";
//      reference "RFC5880, RFC5881";
//
//      container interfaces {
//        description
//          "Interfaces on which BFD sessions are to be enabled.";
//
//        list interface {
//          key "id";
//
//          description
//            "Per-interface configuration and state parameters for BFD.";
//
//          leaf id {
//            type leafref {
//              path "../config/id";
//            }
//            description
//              "A reference to an identifier for the interface on which
//              BFD is enabled.";
//          }
//
//          container config {
//            description
//              "Configuration parameters for BFD on the specified
//              interface.";
//            uses bfd-interface-config;
//          }
//
//
//          uses oc-if:interface-ref;
//
//          uses bfd-interface-microbfd-structural;
//        }
//      }
//    }
//  }

  grouping enable-bfd-config {
    description
      "Configuration parameters relating to enabling BFD.";

    leaf enabled {
      type boolean;
      description
        "When this leaf is set to true, BFD is used to detect the
        liveliness of the remote peer or next-hop.";
    }
  }

  grouping bfd-enable {
    description
      "Grouping which can be included in a protocol wishing to enable
      BFD.";

    container enable-bfd {
      description
        "Enable BFD for liveliness detection to the next-hop or
        neighbour.";

      container config {
        description
          "Configuration parameters relating to enabling BFD.";

        uses enable-bfd-config;
      }
    }
  }
  
//  augment "/ncs:devices/ncs:device/mdd:openconfig" {
//    uses bfd-top;
//  }
}
