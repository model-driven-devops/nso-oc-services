module openconfig-procmon {

  yang-version "1";

  // namespace
  namespace "http://openconfig.net/yang/system/procmon";

  prefix "oc-proc";


  // import some basic types
  import openconfig-extensions { prefix oc-ext; }
  import openconfig-types { prefix oc-types; }
  import openconfig-yang-types { prefix oc-yang; }


  // meta
  organization "OpenConfig working group";

  contact
    "OpenConfig working group
    www.openconfig.net";

  description
    "This module provides data definitions for process health
    monitoring of one or more processes running on the system.";

  oc-ext:openconfig-version "0.4.0";

  revision "2019-03-15" {
    description
      "Update process start time to be an absolute timestamp,
      ensure that the units for CPU time are expressed correctly.
      Update cpu-usage leaves to commonly use counter64 for consumed
      CPU time.";
    reference "0.4.0";
  }

  revision "2018-11-21" {
    description
      "Add OpenConfig module metadata extensions.";
    reference "0.3.1";
  }

  revision "2017-09-18" {
    description
      "Updated to use OpenConfig types modules";
    reference "0.3.0";
  }

  revision "2017-07-06" {
    description
      "Move to oc-inet types, add IETF attribution, add RADIUS
      counters, changed password leaf names to indicate hashed";
    reference "0.2.0";
  }

  revision "2017-01-29" {
    description
      "Initial public release";
    reference "0.1.0";
  }

  // OpenConfig specific extensions for module metadata.
  oc-ext:regexp-posix;
  oc-ext:catalog-organization "openconfig";
  oc-ext:origin "openconfig";

  // grouping statements

//  grouping procmon-processes-top {
//    description
//      "Top level grouping for attributes for processes.";
//
//    container processes {
//      description
//        "Parameters related to all monitored processes";
//
//      list process {
//        key "pid";
//        config false;
//        description
//          "List of monitored processes";
//
//        leaf pid {
//          type leafref {
//            path "../state/pid";
//          }
//          description
//            "Reference to the process pid key";
//        }
//      }
//    }
//  }

  // augment statements

  // rpc statements

  // notification statements
}
