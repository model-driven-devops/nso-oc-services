module openconfig-platform-software {

  yang-version "1";

  // namespace
  namespace "http://openconfig.net/yang/platform/software-module";

  prefix "oc-sw-module";

  import openconfig-platform {
      prefix oc-platform;
  }
  
  import openconfig-extensions {
      prefix oc-ext;
  }

  // meta
  organization
    "OpenConfig working group";

  contact
    "OpenConfig working group
      www.openconfig.net";

  description
    "This module defines data related to software components in
      the openconfig-platform model";

  oc-ext:openconfig-version "0.1.0";

  revision "2021-01-18" {
      description
        "Initial revision.";
      reference "0.1.0";
  }

  // OpenConfig specific extensions for module metadata.
  oc-ext:catalog-organization "openconfig";
  oc-ext:origin "openconfig";

  // extension statements
  // feature statements
  // identity statements
  identity SOFTWARE_MODULE_TYPE {
    description
      "Base identity for defining various types of software
      modules.";
  }

  identity USERSPACE_PACKAGE_BUNDLE {
    base SOFTWARE_MODULE_TYPE;
    description
      "A collection of userspace software modules that are grouped, and
      possibly versioned, together.  A package bundle may have
      subcomponents that represent individual elements in the bundle
      and their properties.";
  }

  identity USERSPACE_PACKAGE {
    base SOFTWARE_MODULE_TYPE;
    description
      "An individual software package that runs in user space. The
      package may be part of a package bundle.";
  }

  // typedef statements
  // grouping statements
  grouping sw-module-state {
    description
      "Operational state data for software module components";

    leaf module-type {
      type identityref {
          base SOFTWARE_MODULE_TYPE;
      }
      description
        "Type of the software module";
    }
  }

  // data definition statements
  // augment statements
  augment "/ncs:devices/ncs:device/mdd:openconfig/oc-platform:components/oc-platform:component/" +
  "oc-platform:software-module/oc-platform:state" {
      description
        "Adding software module operational data to physical inventory.
        This subtree is only valid when the type of the component is
        SOFTWARE_MODULE.";

      uses sw-module-state;
  }
}
